module odltest {
    yang-version 1.1;
    namespace "urn:opendaylight:params:xml:ns:yang:odltest";
    prefix "odltest";

    revision "2017-08-30" { // TODO change revision to date of model creation
        description "Initial revision of odltest model";
    }
}
